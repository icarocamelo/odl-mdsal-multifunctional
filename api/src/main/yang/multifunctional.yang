module multifunctional {
    yang-version 1;
    namespace "urn:opendaylight:params:xml:ns:yang:multifunctional";
    prefix "multifunctional";

    revision "2015-01-05" {
        description "Initial revision of multifunctional model";
    }
}

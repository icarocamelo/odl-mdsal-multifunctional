//This file contains a YANG data definition. This data model defines
  //a toaster, which is based on the SNMP MIB multifunctional example 
  module multifunctional {

    //The yang version - today only 1 version exists. If omitted defaults to 1.
    yang-version 1; 

    //a unique namespace for this multifunctional module, to uniquely identify it from other modules that may have the same name.
    namespace
      "http://inocybe.com/ns/multifunctional"; 

    //a shorter prefix that represents the namespace for references used below
    prefix multifunctional;

    //Defines the organization which defined / owns this .yang file.
    organization "Inocybe Technologies";


    //provides a description of this .yang file.
    description
      "YANG version of the MULTIFUNCTIONAL-MIB.";

    //defines the dates of revisions for this yang file
    revision "2015-08-04" {
      description
        "Multifunctional module in progress.";
    }

    rpc print {
        input {
          leaf numberOfPages{
            type uint32 {
              range "1 .. 10";
            }
            default '5';
            description
            "Number of page to be printed.";
          }
        }
      }

    rpc cancel {
     description
       "Stop printing.";
    }  

    //declares a base identity, in this case a base type for different types of multifunctional.
    identity multifunctional-type {
      description
        "Base for all multifunctional types supported by the Multifunctional. New multifunctional types not listed here nay be added in the future.";
    }

    //the below identity section is used to define globally unique identities
    //Note - removed a number of different types of bread to shorten the text length.
    identity hp-multifunctional {
      base multifunctional:multifunctional-type;       //logically extending the declared toast-type above.
      description "HP multifunctional.";  //free text description of this type.
    }

    //defines a new "Type" string type which limits the length
    typedef DisplayString {
      type string {
        length "0 .. 255";
      }
      description
        "YANG version of the SMIv2 DisplayString TEXTUAL-CONVENTION.";
      reference
        "RFC 2579, section 2.";

    }

    // This definition is the top-level configuration "item" that defines a Multifunctional. The "presence" flag connotes there
    // can only be one instance of a Multifunctional which, if present, indicates the service is available.
    container multifunctional {
      presence
        "Indicates the multifunctional service is available";
      description
        "Top-level container for all multifunctional database objects.";

      //Note in these three attributes that config = false. This indicates that they are operational attributes.
      leaf multifunctionalManufacturer {
        type DisplayString;
        config false;
        mandatory true;
        description
          "The name of the multifunctional's manufacturer. For instance, HP's multifunctional.";
      }

      leaf multifunctionalModelNumber {
        type DisplayString;
        config false;
        mandatory true;
        description
          "The name of the multifunctional's model. For instance, Radiant Automatic.";
      }

      leaf multifunctionalStatus {
        type enumeration {
          enum "up" {
            value 1;
            description
              "The multifunctional knob position is up. No toast is being made now.";
          }
          enum "down" {
            value 2;
            description
              "The multifunctional knob position is down. Toast is being made now.";
          }
        }
        config false;
        mandatory true;
        description
          "This variable indicates the current state of  the multifunctional.";
      }

      

    }  // container multifunctional
  }  // module multifunctional

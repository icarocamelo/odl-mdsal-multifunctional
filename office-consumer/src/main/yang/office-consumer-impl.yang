module office-consumer-impl {

    yang-version 1;
    namespace "urn:opendaylight:params:xml:ns:yang:config:office-consumer-impl";
    prefix "office-consumer-impl";

    import config { prefix config; revision-date 2013-04-05; }
    import rpc-context { prefix rpcx; revision-date 2013-06-17; }

    import opendaylight-md-sal-binding { prefix mdsal; revision-date 2013-10-28; }

    description
        "This module contains the base YANG definitions for
        office-consumer-impl implementation.";

    revision "2014-01-31" {
        description
            "Initial revision.";
    }

    // This is the definition of office service interface identity.
    identity office-consumer {
        base "config:service-type";
        config:java-class "org.opendaylight.controller.office.api.OfficeService";
    }

    // This is the definition of office service implementation module identity. 
    identity office-consumer-impl {
            base config:module-type;
            config:provided-service office-consumer;
            config:java-name-prefix OfficeService;
    }

    augment "/config:modules/config:module/config:configuration" {
        case office-consumer-impl {
            when "/config:modules/config:module/config:type = 'office-consumer-impl'";

            
            container rpc-registry {
                uses config:service-ref {
                    refine type {
                        mandatory true;
                        config:required-identity mdsal:binding-rpc-registry;
                    }
                }
            }
            
            container notification-service {
               uses config:service-ref {
                   refine type {
                       mandatory true;
                       config:required-identity mdsal:binding-notification-service;
                   }
               }
           }
        }
    }
    
    augment "/config:modules/config:module/config:state" {
        case office-consumer-impl {
            when "/config:modules/config:module/config:type = 'office-consumer-impl'";

            rpcx:rpc-context-instance "print-and-send-fax-rpc";
        }
    }

    identity print-and-send-fax-rpc;

    rpc print-and-send-fax  {
        description
          "Shortcut JMX call to print-and-send-fax for testing.";

        input {
            uses rpcx:rpc-context-ref {
                refine context-instance {
                    rpcx:rpc-context-instance print-and-send-fax-rpc;
                }
            }
        }
        output {
            leaf result {
                type boolean;
            }
        }
    }
}

module office-service-impl {

    yang-version 1;
    namespace "urn:opendaylight:params:xml:ns:yang:config:office-service:impl";
    prefix "office-service-impl";

    import config { prefix config; revision-date 2013-04-05; }
    import rpc-context { prefix rpcx; revision-date 2013-06-17; }

    import opendaylight-md-sal-binding { prefix mdsal; revision-date 2013-10-28; }

    description
        "This module contains the base YANG definitions for
        office-service impl implementation.";

    revision "2014-01-31" {
        description
            "Initial revision.";
    }

    // This is the definition of office service interface identity.
    identity office-service {
        base "config:service-type";
        config:java-class "org.opendaylight.controller.office.api.officeService";
    }

    // This is the definition of office service implementation module identity. 
    identity office-service-impl {
            base config:module-type;
            config:provided-service office-service;
            config:java-name-prefix officeService;
    }

    augment "/config:modules/config:module/config:configuration" {
        case office-service-impl {
            when "/config:modules/config:module/config:type = 'office-service-impl'";

            container rpc-registry {
                uses config:service-ref {
                    refine type {
                        mandatory true;
                        config:required-identity mdsal:binding-rpc-registry;
                    }
                }
            }
        }
    }
}
